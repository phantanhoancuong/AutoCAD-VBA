Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True
Private Sub AcadDocument_BeginSave(ByVal FileName As String)

End Sub

Attribute VB_Name = "form_BTVN01"
Attribute VB_Base = "0{824D75BA-4932-4463-AC74-983EF17A9CFC}{3A213F9F-637A-47A8-A56A-30E1B8798E10}"
Attribute VB_GlobalNameSpace = False
Attribute VB_Creatable = False
Attribute VB_PredeclaredId = True
Attribute VB_Exposed = False
Attribute VB_TemplateDerived = False
Attribute VB_Customizable = False
Sub cmd_Draw_Click()
    Dim xA As Double
    Dim yA As Double
    Dim xB As Double
    Dim yB As Double
    
    If Not TryGetDoubleValue(txt_xA.text, xA) Then Exit Sub
    If Not TryGetDoubleValue(txt_yA.text, yA) Then Exit Sub
    If Not TryGetDoubleValue(txt_xB.text, xB) Then Exit Sub
    If Not TryGetDoubleValue(txt_yB.text, yB) Then Exit Sub
    
    Dim lineObj As AcadLine
    Set lineObj = ThisDrawing.ModelSpace.AddLine(CreatePoint(xA, yA), CreatePoint(xB, yB))
    
    ThisDrawing.Application.ZoomExtents
    
    Set lineObj = Nothing
End Sub

Function CreatePoint(ByVal x As Double, ByVal y As Double) As Variant
    Dim point(0 To 2) As Double
    point(0) = x
    point(1) = y
    point(2) = 0
    CreatePoint = point
End Function

Sub cmd_Calculate_Click()
    Dim xA As Double
    Dim yA As Double
    Dim xB As Double
    Dim yB As Double
    Dim xC As Double
    Dim yC As Double
    Dim xD As Double
    Dim yD As Double
    
    ' Convert textbox values to Double with error handling
    If Not TryGetDoubleValue(txt_xA.text, xA) Then Exit Sub
    If Not TryGetDoubleValue(txt_yA.text, yA) Then Exit Sub
    If Not TryGetDoubleValue(txt_xB.text, xB) Then Exit Sub
    If Not TryGetDoubleValue(txt_yB.text, yB) Then Exit Sub
    If Not TryGetDoubleValue(txt_xC.text, xC) Then Exit Sub
    If Not TryGetDoubleValue(txt_yC.text, yC) Then Exit Sub
    
    ' Calculate the projected point D
    CalculateProjectedPoint xA, yA, xB, yB, xC, yC, xD, yD
    
    MsgBox "Projected point D: (" & xD & ", " & yD & ")"
    ' Check if point D lies on segment AB
    If IsPointOnSegment(xA, yA, xB, yB, xD, yD) Then
        ' Display the result
        MsgBox "Projected point D: (" & xD & ", " & yD & ")"
        Dim lineObj As AcadLine
        Set lineObj = ThisDrawing.ModelSpace.AddLine(CreatePoint(xC, yC), CreatePoint(xD, yD))
        Set lineObj = Nothing
        DrawEF xA, yA, xB, yB, xC, yC
        DrawCircleCD xC, yC, xD, yD
        ThisDrawing.Application.ZoomExtents
    Else
        MsgBox "Projected point D does not lie on segment AB."
    End If
End Sub

Sub CalculateProjectedPoint(xA As Double, yA As Double, xB As Double, yB As Double, xC As Double, yC As Double, ByRef xD As Double, ByRef yD As Double)
    Dim xAB As Double
    Dim yAB As Double
    Dim xAC As Double
    Dim yAC As Double
    Dim dot_product As Double
    Dim dAB_squared As Double
    
    xAB = xB - xA
    yAB = yB - yA
    xAC = xC - xA
    yAC = yC - yA
    
    dot_product = xAB * xAC + yAB * yAC
    dAB_squared = xAB * xAB + yAB * yAB
    
    xD = xA + (dot_product / dAB_squared) * xAB
    yD = yA + (dot_product / dAB_squared) * yAB
End Sub

Function TryGetDoubleValue(text As String, ByRef value As Double) As Boolean
    On Error Resume Next
    value = CDbl(text)
    If Err.Number <> 0 Then
        MsgBox "Invalid value entered."
        TryGetDoubleValue = False
        Err.Clear
    Else
        TryGetDoubleValue = True
    End If
    On Error GoTo 0
End Function

Function IsPointOnSegment(ByVal xA As Double, ByVal yA As Double, ByVal xB As Double, ByVal yB As Double, ByVal xD As Double, ByVal yD As Double) As Boolean
    Dim dAD As Double
    Dim dBD As Double
    Dim dAB As Double
    
    dAD = Sqr((xA - xD) ^ 2 + (yA - yD) ^ 2)
    dBD = Sqr((xB - xD) ^ 2 + (yB - yD) ^ 2)
    dAB = Sqr((xA - xB) ^ 2 + (yA - yB) ^ 2)
    
    If Abs(dAD + dBD - dAB) < 0.000001 Then
        IsPointOnSegment = True
    Else
        IsPointOnSegment = False
    End If
End Function

Sub DrawEF(ByVal xA As Double, ByVal yA As Double, ByVal xB As Double, ByVal yB As Double, ByVal xC As Double, ByVal yC As Double)
    Dim xE As Double
    Dim yE As Double
    Dim xF As Double
    Dim yF As Double
    
    xE = xC + (xA - xB) * (1 / 3)
    yE = yC + (yA - yB) * (1 / 3)
    
    xF = xC - (xA - xB) * (2 / 3)
    yF = yC - (yA - yB) * (2 / 3)
    
    Dim lineObj As AcadLine
    Set lineObj = ThisDrawing.ModelSpace.AddLine(CreatePoint(xE, yE), CreatePoint(xF, yF))
    Set lineObj = Nothing
    
    DrawSplineAEF xA, yA, xE, yE, xF, yF
End Sub

Sub DrawSplineAEF(ByVal xA As Double, ByVal yA As Double, ByVal xE As Double, ByVal yE As Double, ByVal xF As Double, ByVal yF As Double)

    ' Create the spline
    Dim splineObj As AcadSpline
    Dim startTan(0 To 2) As Double
    Dim endTan(0 To 2) As Double
    Dim fitPoints(0 To 8) As Double
    
    startTan(0) = 0.5: startTan(1) = 0.5: startTan(2) = 0
    endTan(0) = 0.5: endTan(1) = 0.5: endTan(2) = 0
    fitPoints(0) = xE: fitPoints(1) = yE: fitPoints(2) = 0
    fitPoints(3) = xA: fitPoints(4) = yA: fitPoints(5) = 0
    fitPoints(6) = xF: fitPoints(7) = yF: fitPoints(8) = 0
    Set splineObj = ThisDrawing.ModelSpace.AddSpline(fitPoints, startTan, endTan)

End Sub

Sub DrawCircleCD(ByVal xC As Double, ByVal yC As Double, ByVal xD As Double, ByVal yD As Double)
    Dim radius As Double
    
    radius = Sqr((xD - xC) ^ 2 + (yD - yC) ^ 2)
    
    Dim circleObj As AcadCircle
    
    Set circleObj = ThisDrawing.ModelSpace.AddCircle(CreatePoint(xC, yC), radius)
End Sub
