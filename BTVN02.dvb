Attribute VB_Name = "form_BTVN02"
Attribute VB_Base = "0{F5FD74F0-F37D-43B3-AFB7-0E8F076C608C}{99D1A933-9FB8-4D82-844E-90BE090C7F51}"
Attribute VB_GlobalNameSpace = False
Attribute VB_Creatable = False
Attribute VB_PredeclaredId = True
Attribute VB_Exposed = False
Attribute VB_TemplateDerived = False
Attribute VB_Customizable = False
Sub cmd_DrawCircleCenterRadius_Click()
    ' Get the coordinates from the textboxes
    Dim xCenter As Double
    Dim yCenter As Double
    Dim radius As Double
    
    ' Convert textbox values to Double with error handling
    If Not TryGetDoubleValue(txt_xCenter.text, xCenter) Then Exit Sub
    If Not TryGetDoubleValue(txt_yCenter.text, yCenter) Then Exit Sub
    If Not TryGetDoubleValue(txt_CircleRadius.text, radius) Then Exit Sub
    
    ' Add a line object connecting points A and B
    Dim circleObj As AcadCircle
    Set circleObj = ThisDrawing.ModelSpace.AddCircle(CreatePoint(xCenter, yCenter), radius)
    
    ' Zoom to show the entire drawing
    ThisDrawing.Application.ZoomExtents
    
    ' Clean up the line object reference
    Set circleObj = Nothing
    
    ThisDrawing.Regen acAllViewports
End Sub

Sub cmd_DrawCircleOffset_Click()
    ' Get the coordinates from the textboxes
    Dim xCenter As Double
    Dim yCenter As Double
    Dim radius As Double
    Dim offset As Double
    
    ' Convert textbox values to Double with error handling
    If Not TryGetDoubleValue(txt_xCenter.text, xCenter) Then Exit Sub
    If Not TryGetDoubleValue(txt_yCenter.text, yCenter) Then Exit Sub
    If Not TryGetDoubleValue(txt_CircleRadius.text, radius) Then Exit Sub
    If Not TryGetDoubleValue(txt_Offset.text, offset) Then Exit Sub
    
    ' Add a line object connecting points A and B
    Dim circleObj As AcadCircle
    Set circleObj = ThisDrawing.ModelSpace.AddCircle(CreatePoint(xCenter, yCenter), radius - offset)
    
    ' Zoom to show the entire drawing
    ThisDrawing.Application.ZoomExtents
    
    ' Clean up the line object reference
    Set circleObj = Nothing
    
    ThisDrawing.Regen acAllViewports
End Sub

Sub cmd_DrawCircleTangentsRadius_Click()
    ' Get the coordinates from the textboxes
    Dim xTangent1 As Double
    Dim yTangent1 As Double
    Dim xTangent2 As Double
    Dim yTangent2 As Double
    Dim radius As Double
    Dim command As String
    
    ' Convert textbox values to Double with error handling
    If Not TryGetDoubleValue(txt_xTangent1.text, xTangent1) Then Exit Sub
    If Not TryGetDoubleValue(txt_yTangent1.text, yTangent1) Then Exit Sub
    If Not TryGetDoubleValue(txt_xTangent2.text, xTangent2) Then Exit Sub
    If Not TryGetDoubleValue(txt_yTangent2.text, yTangent2) Then Exit Sub
    If Not TryGetDoubleValue(txt_CircleRadius.text, radius) Then Exit Sub
    
    ' Build the command string for adding the circle
    command = "CIRCLE TTR " & xTangent1 & "," & yTangent1 & " " & xTangent2 & "," & yTangent2 & " " & radius
    
    ' Send the command to AutoCAD
    ThisDrawing.SendCommand command & vbCr

    ThisDrawing.Application.ZoomExtents
    
    ThisDrawing.Regen acAllViewports
End Sub

' Create a point with the given x, y coordinates
Function CreatePoint(ByVal x As Double, ByVal y As Double) As Variant
    Dim point(0 To 2) As Double
    point(0) = x
    point(1) = y
    point(2) = 0
    CreatePoint = point
End Function

' Convert the text value to Double and handle errors
Function TryGetDoubleValue(text As String, ByRef value As Double) As Boolean
    On Error Resume Next
    value = CDbl(text)
    If Err.Number <> 0 Then
        MsgBox "Invalid value entered."
        TryGetDoubleValue = False
        Err.Clear
    Else
        TryGetDoubleValue = True
    End If
    On Error GoTo 0
End Function

Sub cmd_DrawArc_Click()
    ' Get the coordinates from the textboxes
    Dim xStart As Double
    Dim yStart As Double
    Dim xEnd As Double
    Dim yEnd As Double
    Dim radius As Double
    Dim command As String
    
    ' Convert textbox values to Double with error handling
    If Not TryGetDoubleValue(txt_xArcStart.text, xStart) Then Exit Sub
    If Not TryGetDoubleValue(txt_yArcStart.text, yStart) Then Exit Sub
    If Not TryGetDoubleValue(txt_xArcEnd.text, xEnd) Then Exit Sub
    If Not TryGetDoubleValue(txt_yArcEnd.text, yEnd) Then Exit Sub
    If Not TryGetDoubleValue(txt_ArcRadius.text, radius) Then Exit Sub
        
    command = "ARC " & Format(xStart, "0.0000") & "," & Format(yStart, "0.0000") & " " & Format(xEnd, "0.0000") & "," & Format(yEnd, "0.0000") & " " & Format(radius, "0.0000")
    ' Zoom to show the entire drawing
    ThisDrawing.SendCommand command

    ThisDrawing.Application.ZoomExtents
    
    ThisDrawing.Regen acAllViewports
    
End Sub

Sub cmd_DrawSegment_Click()
    ' Get the coordinates from the textboxes
    Dim xStart As Double
    Dim yStart As Double
    Dim xEnd As Double
    Dim yEnd As Double
    
    ' Convert textbox values to Double with error handling
    If Not TryGetDoubleValue(txt_xSegmentStart.text, xStart) Then Exit Sub
    If Not TryGetDoubleValue(txt_ySegmentStart.text, yStart) Then Exit Sub
    If Not TryGetDoubleValue(txt_xSegmentEnd.text, xEnd) Then Exit Sub
    If Not TryGetDoubleValue(txt_ySegmentEnd.text, yEnd) Then Exit Sub
    
    Dim lineObj As AcadLine
    Set lineObj = ThisDrawing.ModelSpace.AddLine(CreatePoint(xStart, yStart), CreatePoint(xEnd, yEnd))
    
    ThisDrawing.Application.ZoomExtents
    
    ThisDrawing.Regen acAllViewports
    
    Set lineObj = Nothing
End Sub
